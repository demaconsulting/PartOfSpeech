package PartOfSpeech {
    part def Demo {
        doc /* Demonstration greeting class showing how a DEMA Consulting .NET library class should be structured, documented, and tested. */

        comment sourceRef /* Source: src/DemaConsulting.PartOfSpeech/Demo.cs */
        comment testRef /* Test: test/DemaConsulting.PartOfSpeech.Tests/DemoTests.cs */
        comment designRef /* Design: docs/design/part-of-speech/demo.md */
        comment verificationRef /* Verification: docs/verification/part-of-speech/demo.md */
        comment reqRef /* Requirements: docs/reqstream/part-of-speech/demo.yaml */
    }
}
